module mw-e2e-runtime {
    yang-version 1;
    namespace "urn:mw:metro:runtime:impl";
    prefix "mw-e2e-runtime";

    import config { prefix config; revision-date 2013-04-05; }
    import driver-register {prefix driver-register; revision-date 2017-09-18;}
    import mw-e2e-runtime-api { prefix mw-e2e-runtime-api; revision-date 2017-09-17; }
    import connection-provider { prefix connection-provider; revision-date 2017-09-18;}
    import opendaylight-md-sal-binding { prefix mdsal; revision-date 2013-10-28; }

    organization "ZTE";

    revision "2017-09-17" {
        description
            "Initial revision";
    }

    identity mw-e2e-runtime-builder {
         base config:module-type;
         config:provided-service mw-e2e-runtime-api:mw-base-environment;
         config:java-name-prefix MicrowaveRuntime;
    }

    augment "/config:modules/config:module/config:configuration" {
         case mw-e2e-runtime-builder {
              when "/config:modules/config:module/config:type = 'mw-e2e-runtime-builder'";
              leaf name-prefix {
                  type string;
              }
            container driver-register {
                uses config:service-ref {
                    refine type {
                        mandatory true;
                        config:required-identity driver-register:service-driver-register;
                    }
                }
            }
            container connection-provider {
                uses config:service-ref {
                    refine type {
                        mandatory true;
                        config:required-identity connection-provider:service-connection-provider;
                    }
                }
            }
         }
    }
}
