module pce-thread-pool {
    yang-version 1;
    namespace "urn:zte:ngip:ipsdn:pce:thread:pool";
    prefix "pce-thread-pool";

    import config { prefix config; revision-date 2013-04-05; }
    import pce-api-cfg { prefix pce-api-cfg; revision-date 2017-03-30; }

    organization "ZTE";

    revision "2017-04-06" {
        description
            "Initial revision";
    }

    identity pce-thread-factory-builder {
         base config:module-type;
         config:provided-service pce-api-cfg:pce-threadfactory;
         config:java-name-prefix PceThreadFactory;
    }

    augment "/config:modules/config:module/config:configuration" {
         case pce-thread-factory-builder {
              when "/config:modules/config:module/config:type = 'pce-thread-factory-builder'";
              leaf name-prefix {
                  type string;
              }
         }
    }
}
