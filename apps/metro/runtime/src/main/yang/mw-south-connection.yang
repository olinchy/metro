module mw-e2e-runtime {
    yang-version 1;
    namespace "urn:mw:metro:runtime";
    prefix "mw-e2e-runtime";

    import config { prefix config; revision-date 2013-04-05; }

    organization "ZTE";

    revision "2017-09-16" {
        description
            "Initial revision";
    }

    identity mw-base-environment {
        description
            "Service representing a infrastructure of microwave instance.";
        base "config:service-type";
        config:java-class "com.zte.ngip.ipsdn.pce.path.api.thread.ThreadFactoryGenerator";
    }

    identity mw-e2e-runtime {
         base config:module-type;
         config:provided-service pce-api-cfg:pce-threadfactory;
         config:java-name-prefix PceThreadFactory;
    }

    augment "/config:modules/config:module/config:configuration" {
         case pce-thread-factory-builder {
              when "/config:modules/config:module/config:type = 'pce-thread-factory-builder'";
              leaf name-prefix {
                  type string;
              }
         }
    }
}
