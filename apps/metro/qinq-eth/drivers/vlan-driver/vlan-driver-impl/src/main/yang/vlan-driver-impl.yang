module vlan-driver-impl {
    yang-version 1;
    namespace "urn:zte:sdn:mw:vlan:driver:impl";
    prefix "vlan-driver-impl";

    import config { prefix config; revision-date 2013-04-05; }
    import opendaylight-md-sal-binding { prefix mdsal; revision-date 2013-10-28;}

    description
        "Service definition for vlan-driver project";

    revision "2017-09-13" {
        description
            "Initial revision";
    }

    identity vlan-driver-impl {
        base config:module-type;
        config:java-name-prefix VlanDriver;
    }

    augment "/config:modules/config:module/config:configuration" {
        case vlan-driver-impl {
            when "/config:modules/config:module/config:type = 'vlan-driver-impl'";

            container rpc-registry {
                uses config:service-ref {
                    refine type {
                        mandatory true;
                        config:required-identity mdsal:binding-rpc-registry;
                    }
                }
            }

            container data-broker {
                uses config:service-ref {
                    refine type {
                        mandatory false;
                        config:required-identity mdsal:binding-async-data-broker;
                    }
                }
            }

            container notification-service {
                uses config:service-ref {
                    refine type {
                        mandatory true;
                        config:required-identity mdsal:binding-notification-service;
                    }
                }
            }
        }
    }
}
