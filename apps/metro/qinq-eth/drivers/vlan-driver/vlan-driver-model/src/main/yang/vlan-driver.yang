module vlan-driver {
    yang-version 1;
    namespace "urn:zte:sdn:mw:vlan:driver";
    prefix "vlan-driver";

    revision "2017-9-13" {
        description "Initial revision of vlan-driver model";
    }
}
