module notification-listener-impl {
    yang-version 1;
    namespace "urn:zte:mw:sdn:notification:listener:impl";
    prefix "notification-listener-impl";

    import config { prefix config; revision-date 2013-04-05; }
    import opendaylight-md-sal-binding { prefix mdsal; revision-date 2013-10-28;}
    import mw-e2e-runtime-api { prefix mw-e2e-runtime-api; revision-date 2017-09-17; }
    import pce-path-calculator { prefix pce-path-calculator; revision-date 2017-09-19; }

    description
        "Service definition for notification-listener project";

    revision "2017-09-13" {
        description
            "Initial revision";
    }

    identity notification-listener-impl {
        base config:module-type;
        config:java-name-prefix NotificationListener;
    }

    augment "/config:modules/config:module/config:configuration" {
        case notification-listener-impl {
            when "/config:modules/config:module/config:type = 'notification-listener-impl'";

            container data-broker {
                uses config:service-ref {
                    refine type {
                        mandatory false;
                        config:required-identity mdsal:binding-async-data-broker;
                    }
                }
            }
            container mw-runtime-service {
                 uses config:service-ref {
                      refine type {
                            mandatory true;
                            config:required-identity mw-e2e-runtime-api:mw-base-environment;
                      }
                 }
            }
            container mw-pce-path-calculator {
                 uses config:service-ref {
                      refine type {
                            mandatory true;
                            config:required-identity pce-path-calculator:service-pce-path-calculator;
                      }
                 }
            }
        }
    }
}
