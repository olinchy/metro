module nbi-rpc {
    yang-version 1;
    namespace "urn:zte:mw:sdn:nbi:rpc";
    prefix "nbi-rpc";

    revision "2017-09-13" {
        description "Initial revision of nbi-rpc model";
    }

    organization "ZTE";
}
