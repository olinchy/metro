module pce-path-impl {
    yang-version 1;
    namespace "urn:zte:ngip:ipsdn:pce-path-impl";
    prefix "pce-path-impl";

    import config { prefix config; revision-date 2013-04-05; }
    import opendaylight-md-sal-binding { prefix md-sal-binding; revision-date 2013-10-28;}
    import pce-api-cfg { prefix pce-api-cfg; revision-date 2017-03-30; }
    import pce-path-calculator { prefix pce-path-calculator; revision-date 2017-09-19; }

    description
        "Service definition for pce-path-impl project";

    revision "2014-12-10" {
        description
            "Initial revision";
    }

    identity pce-path-impl {
        base config:module-type;
        config:provided-service pce-path-calculator:service-pce-path-calculator;
        config:java-name-prefix PcePath;
    }

    augment "/config:modules/config:module/config:configuration" {
        case pce-path-impl {
            when "/config:modules/config:module/config:type = 'pce-path-impl'";

            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-service {
                uses config:service-ref {
                    refine type {
                        mandatory true;
                        config:required-identity md-sal-binding:binding-notification-service;
                    }
                }
            }
            container pce-toporovider-service {
                uses config:service-ref {
                     refine type {
                         mandatory true;
                         config:required-identity pce-api-cfg:pce-topo-provider-service;
                     }
                }
            }
            container pce-topo-change-service {
                uses config:service-ref {
                     refine type {
                         mandatory true;
                         config:required-identity pce-api-cfg:topo-change-service;
                     }
                }
            }

            container pce-factory-service {
                uses config:service-ref {
                     refine type {
                           mandatory true;
                           config:required-identity pce-api-cfg:pce-threadfactory;
                     }
                }
            }

            container pce-label-encoding-service {
                uses config:service-ref {
                     refine type {
                           mandatory true;
                           config:required-identity pce-api-cfg:pce-label-encoding-service;
                     }
                }
            }
            leaf can-zero-band-width {
                 type boolean;
            }
        }
    }
}
