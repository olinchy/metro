module mw-vlan-function {
    yang-version 1;
    namespace "urn:zte:ngip:ipsdn:function:mw-vlan-function";
    prefix "mw-vlan-function";

    import qinq-service-model {prefix qinq-service-model;revision-date "2017-09-05";}

    organization "zte";
    contact "zte";
    description "mw-vlan-function";

    revision "2017-09-11" {
        description "Initial revision of vlan model";
    }


    rpc create-vlan {
        input {
            leaf name {
                type leafref {
                    path '/qinq-service-model:mw-l2vpn/qinq-service-model:qinq-service-instance/qinq-service-model:name';
                }
            }
            leaf txid {
                type leafref {
                    path '/qinq-service-model:mw-l2vpn/qinq-service-model:qinq-service-instance/qinq-service-model:txid';
                }
            }
        }
    }

    rpc delete-vlan {
        input {
            leaf name {
                type leafref {
                    path '/qinq-service-model:mw-l2vpn/qinq-service-model:qinq-service-instance/qinq-service-model:name';
                }
            }
            leaf txid {
                type leafref {
                    path '/qinq-service-model:mw-l2vpn/qinq-service-model:qinq-service-instance/qinq-service-model:txid';
                }
            }
        }
    }
}
