module pce-path-calculator-impl {
    yang-version 1;
    namespace "urn:zte:sdn:mw:pce:path:calculator:impl";
    prefix "pce-path-calculator-impl";

    import config { prefix config; revision-date 2013-04-05; }
    import opendaylight-md-sal-binding { prefix md-sal-binding; revision-date 2013-10-28;}
    import pce-api-cfg { prefix pce-api-cfg; revision-date 2017-03-30; }
    import pce-path-calculator { prefix pce-path-calculator; revision-date 2017-09-19;}

    organization "ZTE";

    description
        "Service implementation for pce-path-calculator project";

    revision "2017-09-19" {
        description
            "Initial revision";
    }

    identity pce-path-calculator-impl {
         base config:module-type;
         config:provided-service pce-path-calculator:service-pce-path-calculator;
         config:java-name-prefix PcePathCalculator;
    }

    augment "/config:modules/config:module/config:configuration" {
         case pce-path-calculator-impl {
              when "/config:modules/config:module/config:type = 'pce-path-calculator-impl'";
              leaf name-prefix {
                  type string;
              }
            container data-broker {
                uses config:service-ref {
                    refine type {
                        mandatory true;
                        config:required-identity md-sal-binding:binding-async-data-broker;
                    }
                }
            }
            container notification-service {
                uses config:service-ref {
                    refine type {
                        mandatory true;
                        config:required-identity md-sal-binding:binding-notification-service;
                    }
                }
            }
            container pce-toporovider-service {
                uses config:service-ref {
                     refine type {
                         mandatory true;
                         config:required-identity pce-api-cfg:pce-topo-provider-service;
                     }
                }
            }
            container pce-topo-change-service {
                uses config:service-ref {
                     refine type {
                         mandatory true;
                         config:required-identity pce-api-cfg:topo-change-service;
                     }
                }
            }

            container pce-factory-service {
                uses config:service-ref {
                     refine type {
                           mandatory true;
                           config:required-identity pce-api-cfg:pce-threadfactory;
                     }
                }
            }

            container pce-label-encoding-service {
                uses config:service-ref {
                     refine type {
                           mandatory true;
                           config:required-identity pce-api-cfg:pce-label-encoding-service;
                     }
                }
            }
            leaf can-zero-band-width {
                 type boolean;
            }
         }
    }
}
