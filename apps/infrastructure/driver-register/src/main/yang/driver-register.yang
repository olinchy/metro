module driver-register {
    yang-version 1;
    namespace "urn:zte:mw:sdn:driver:register";
    prefix "driver-register";

    import config { prefix config; revision-date 2013-04-05; }

    organization "ZTE";

    revision "2017-09-18" {
        description
            "Initial revision of driver-register model";
    }

    identity service-driver-register {
        description
            "Service representing a infrastructure of driver-register instance.";
        base "config:service-type";
        config:java-class "com.zte.mw.sdn.components.DriverRegister";
    }

}
